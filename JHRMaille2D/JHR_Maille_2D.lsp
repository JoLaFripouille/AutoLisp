;;; JHR - panneaux de remplissage 2D, contours fermes, millimetres.
;;; JHRMAILLE / JHRMAILLEPARAM. Aucun contour source modifie.
;;; Cables : largeur geometrique reelle ; composants et contenu sur calque 0.
;;; Les accessoires sont une representation, pas un gabarit de sertissage.
(vl-load-com)
(if (not *wm:cfg*)
  (setq *wm:cfg* '((mw . 60.0) (ml . 104.0) (wire . 1.5) (lace . 2.0)
    (gap . 20.0) (sleeve-l . 5.5) (sleeve-h . 5.7) (angle . 0.0)
    (stops . 12) (maxnodes . 15000))))
;; Preserve session settings when reloading an older configuration.
(if (not (assoc 'corner-auto *wm:cfg*))
  (setq *wm:cfg* (append *wm:cfg* '((corner-auto . 1)))))
;; Old session configurations keep their values; default remains sleeved.
(if (not (assoc 'woven *wm:cfg*)) (setq *wm:cfg* (append *wm:cfg* '((woven . 0)))))
;; Portable folder lookup; manual NETLOAD also works without a support path.
(setq *wm:ui-root* (cond
  ((findfile "JhrMailleUi_v1_3_3r1.dll") (vl-filename-directory (findfile "JhrMailleUi_v1_3_3r1.dll")))
  ((findfile "JHR_Maille_2D.lsp") (vl-filename-directory (findfile "JHR_Maille_2D.lsp")))
  (*wm:ui-root* *wm:ui-root*) (T nil)))
(defun wm:tail (n items) (repeat n (setq items (cdr items))) items)
(defun wm:product-stamp ()
 (mapcar 'wm:cfg '(ml mw wire woven sleeve-l sleeve-h)))
(defun wm:product-current ()
 (if (and *wm:product* (equal *wm:product-stamp* (wm:product-stamp) 1e-8)) *wm:product*))
(defun wm:product-xdata ()
 (if (wm:product-current)
  (mapcar '(lambda (v) (cons 1000 v))
   (mapcar 'strcat '("reference_jakob=" "gamme=" "matiere_catalogue=") (wm:product-current)))))
(if (not *wm:tool*) (setq *wm:tool* 0))
(if (not *wm:patterns*)
 (setq *wm:patterns* '(30.0 30.0 3.0 1.0 0.0 0.0 0.0 0
  40.0 20.0 2.0 1.5 0.0 0.0 0.0 0
  6.0 10.0 1.0 2.0 0.0 0.0 10.0 1)))
(defun wm:half () (if (= (wm:cfg 'woven) 1) (* 2.5 (wm:cfg 'wire)) (/ (wm:cfg 'sleeve-l) 2.0)))
(defun wm:settings-valid (/ join)
 (setq join (* 2.0 (wm:half)))
 (if (or (<= (wm:cfg 'wire) 0) (<= (wm:cfg 'lace) 0) (<= (wm:cfg 'gap) 0)
   (<= (wm:cfg 'ml) (+ join (* 2 (wm:cfg 'wire))))
   (<= (wm:cfg 'mw) (* 4 (wm:cfg 'wire))))
   (wm:fail "Dimensions de maille trop petites pour le cable et la jonction. Verifier les parametres.")))
(defun wm:fail (msg) (setq wm:reason msg) (exit))
(defun wm:floor (x) (if (< x (fix x)) (1- (fix x)) (fix x)))
(defun wm:cfg (k) (cdr (assoc k *wm:cfg*)))
(defun wm:set (k v) (setq *wm:cfg* (subst (cons k v) (assoc k *wm:cfg*) *wm:cfg*)))
(defun wm:add (a b) (mapcar '+ a b))
(defun wm:sub (a b) (mapcar '- a b))
(defun wm:mul (a s) (mapcar '(lambda (v) (* v s)) a))
(defun wm:dot (a b) (+ (* (car a) (car b)) (* (cadr a) (cadr b))))
(defun wm:cross (a b) (- (* (car a) (cadr b)) (* (cadr a) (car b))))
(defun wm:len (a) (sqrt (wm:dot a a)))
(defun wm:unit (a / l) (setq l (wm:len a)) (if (> l 1e-9) (wm:mul a (/ 1.0 l)) '(1.0 0.0)))
(defun wm:lerp (a b t0) (wm:add a (wm:mul (wm:sub b a) t0)))
(defun wm:rot (p ang) (list (- (* (car p) (cos ang)) (* (cadr p) (sin ang))) (+ (* (car p) (sin ang)) (* (cadr p) (cos ang)))))
(defun wm:local (p) (wm:rot (wm:sub (list (car p) (cadr p)) wm:origin) (- wm:angle)))
(defun wm:poly (en / end i n j p bul d0 d1 out)
  (setq end (fix (vlax-curve-getEndParam en)) i 0 out nil)
  (repeat end
    (setq bul (vla-GetBulge (vlax-ename->vla-object en) i)
          d0 (vlax-curve-getDistAtParam en i) d1 (vlax-curve-getDistAtParam en (1+ i))
          n (if (< (abs bul) 1e-10) 1 (max 4 (fix (+ 1 (/ (- d1 d0) 3.0))))) j 0)
    (repeat n (setq p (vlax-curve-getPointAtParam en (+ i (/ (float j) n))) out (cons (wm:local p) out) j (1+ j)))
    (setq i (1+ i)))
  (reverse out))
(defun wm:edges (p) (mapcar 'list p (append (cdr p) (list (car p)))))
(defun wm:area (p / s e) (setq s 0.0) (foreach e (wm:edges p) (setq s (+ s (wm:cross (car e) (cadr e))))) (/ s 2.0))
(defun wm:near (p poly / best bd chain e a b v t0 q dist len)
  (setq bd 1e99 chain 0.0)
  (foreach e (wm:edges poly)
    (setq a (car e) b (cadr e) v (wm:sub b a) len (wm:len v))
    (if (> len 1e-9)
      (progn (setq t0 (max 0.0 (min 1.0 (/ (wm:dot (wm:sub p a) v) (* len len)))) q (wm:lerp a b t0) dist (distance p q))
        (if (< dist bd) (setq bd dist best (list q (wm:unit v) (+ chain (* len t0)))))
        (setq chain (+ chain len)))))
  best)
(defun wm:inside (p poly / odd e a b x y)
  (setq odd nil x (car p) y (cadr p))
  (if (< (distance p (car (wm:near p poly))) 1e-6) T
    (progn (foreach e (wm:edges poly)
      (setq a (car e) b (cadr e))
      (if (and (not (equal (> (cadr a) y) (> (cadr b) y)))
        (< x (+ (car a) (* (- y (cadr a)) (/ (- (car b) (car a)) (- (cadr b) (cadr a)))))))
        (setq odd (not odd)))) odd)))
(defun wm:hit (a b c d / r s det t0 u)
  (setq r (wm:sub b a) s (wm:sub d c) det (wm:cross r s))
  (if (> (abs det) 1e-10)
    (progn (setq t0 (/ (wm:cross (wm:sub c a) s) det) u (/ (wm:cross (wm:sub c a) r) det))
      (if (and (>= t0 -1e-8) (<= t0 1.00000001) (>= u -1e-8) (<= u 1.00000001)) (max 0.0 (min 1.0 t0))))))
(defun wm:breaks (a b polys / ts poly edge v)
  (setq ts '(0.0 1.0))
  (foreach poly polys (foreach edge (wm:edges poly) (if (setq v (wm:hit a b (car edge) (cadr edge))) (setq ts (cons v ts)))))
  (vl-sort ts '<))
(defun wm:clip (a b poly / ts s e mid out)
  (setq ts (wm:breaks a b (list poly)) out nil)
  (while (cdr ts)
    (setq s (car ts) e (cadr ts) mid (wm:lerp a b (/ (+ s e) 2.0)))
    (if (and (> (- e s) 1e-8) (wm:inside mid poly)) (setq out (cons (list (wm:lerp a b s) (wm:lerp a b e)) out)))
    (setq ts (cdr ts))) (reverse out))
(defun wm:pline-data (pts width closed / r)
  (setq r (list '(0 . "LWPOLYLINE") '(100 . "AcDbEntity") '(8 . "0") '(62 . 256) '(6 . "Continuous") '(370 . -1)
    '(100 . "AcDbPolyline") (cons 90 (length pts)) (cons 70 (if closed 1 0)) (cons 43 width)))
  (append r (mapcar '(lambda (p) (cons 10 p)) pts)))
(defun wm:draw (pts width closed) (setq wm:shapes (cons (wm:pline-data pts width closed) wm:shapes)))
(defun wm:insert-data (name p ang)
  (list '(0 . "INSERT") '(100 . "AcDbEntity") '(8 . "0") '(62 . 256) '(6 . "Continuous")
    '(100 . "AcDbBlockReference") (cons 2 name) (cons 10 (append p '(0.0))) '(41 . 1.0) '(42 . 1.0) '(43 . 1.0) (cons 50 ang)))
(defun wm:insert (name p ang) (setq wm:shapes (cons (wm:insert-data name p ang) wm:shapes)))
(defun wm:bezier (a b c d / i t0 u pts)
  (setq i 0 pts nil)
  (repeat 17 (setq t0 (/ i 16.0) u (- 1.0 t0) pts (cons
    (wm:add (wm:add (wm:mul a (* u u u)) (wm:mul b (* 3 u u t0)))
      (wm:add (wm:mul c (* 3 u t0 t0)) (wm:mul d (* t0 t0 t0)))) pts) i (1+ i))) (reverse pts))
(defun wm:key (p) (strcat (rtos (car p) 2 4) ":" (rtos (cadr p) 2 4)))
(defun wm:cut (p grid-a grid-b poly / key target info kind)
  (setq key (wm:key p))
  (if (not (assoc key wm:cuts))
    (progn (setq target
      (cond ((not (wm:inside grid-a poly)) grid-a) ((not (wm:inside grid-b poly)) grid-b) (T p))
      info (wm:near p wm:inner) kind (if (> (abs (car (cadr info))) 0.7071) "LOOP" "EYE"))
      (setq wm:cuts (cons (list key (strcat kind ":" (wm:key target)) kind p) wm:cuts)))))
(defun wm:circle-points (centre radius / j pts)
  (setq j 0 pts nil) (repeat 25
    (setq pts (cons (wm:add centre (list (* radius (cos (* 2 pi (/ j 24.0)))) (* radius (sin (* 2 pi (/ j 24.0)))))) pts) j (1+ j)))
  (reverse pts))
(defun wm:ray-near (p normal poly / ray ts e v)
  (setq ray (wm:add p (wm:mul normal 10000.0)) ts nil)
  (foreach e (wm:edges poly)
    (if (setq v (wm:hit p ray (car e) (cadr e)))
      (if (> v 1e-7) (setq ts (cons v ts)))))
  (if ts (wm:near (wm:lerp p ray (apply 'min ts)) poly) (wm:near p poly)))
(defun wm:terminals (/ groups rec group pts p info tangent normal sign bow anchor a b count)
  (setq groups nil wm:anchors nil sign (if (> (wm:area wm:inner) 0) 1.0 -1.0) wm:eyes 0 wm:loops 0)
  (foreach rec wm:cuts
    (setq group (assoc (cadr rec) groups))
    (if group (setq groups (subst (list (car group) (cadr group) (cons (cadddr rec) (caddr group)) (nth 3 group)) group groups))
      (setq groups (cons (list (cadr rec) (caddr rec) (list (cadddr rec)) (nth 4 rec)) groups))))
  (foreach group groups
    (setq pts (caddr group) count (length pts) p '(0.0 0.0))
    (foreach a pts (setq p (wm:add p a))) (setq p (wm:mul p (/ 1.0 count))
      info (wm:near p wm:inner) tangent (cadr info)
      normal (if (nth 3 group) (nth 3 group) (wm:mul (list (cadr tangent) (- (car tangent))) sign)))
    (if (= (cadr group) "LOOP")
      (progn (setq anchor p wm:loops (1+ wm:loops)))
      (progn
        ;; Eye replaces the sleeve at the outward vertex of a whole diamond.
        (setq p (wm:sub p (wm:mul normal (wm:half))))
        (wm:insert "JHR_WEBNET_OEIL_0150_B16_H8_3_V1" p (angle '(0.0 0.0) normal))
        (setq anchor (wm:add p (wm:mul normal 12.0)) wm:eyes (1+ wm:eyes))))
    (setq info (if (nth 3 group) (wm:ray-near anchor normal wm:inner) (wm:near anchor wm:inner)))
    (setq wm:anchors (cons (list (caddr info) anchor (cadr group) (nth 3 group)) wm:anchors))))
;; A rejected whole cell can leave a three-leg node near a frame corner.
;; Complete only its missing diagonal, when that grid endpoint AND the entire
;; cable fit within the inset polygon. End it with a lateral eye, not a bead.
(defun wm:tip-normal (tip direction / edges previous e t1 t2 n1 n2 normal best bd dist)
  (setq edges (wm:edges wm:inner) previous (car (reverse edges)) bd 1e99)
  (foreach e edges
    (setq t1 (wm:unit (wm:sub (cadr previous) (car previous)))
      t2 (wm:unit (wm:sub (cadr e) (car e))) dist (distance tip (car e)))
    (if (and (> (wm:cross t1 t2) 1e-6) (< (wm:dot t1 t2) 0.8660254)
             (< dist bd) (<= dist (wm:len (list (wm:cfg 'ml) (wm:cfg 'mw)))))
      (progn
        (setq n1 (list (cadr t1) (- (car t1))) n2 (list (cadr t2) (- (car t2)))
          normal (if (> (abs (car n1)) (abs (car n2))) n1 n2))
        (if (> (wm:dot direction normal) 1e-6) (setq best normal bd dist))))
    (setq previous e)) best)
(defun wm:missing-edges (nodes poly sx sy / extra tips found p neighbors tip key normal parts a b swap)
  (setq extra nil tips nil wm:extensions 0)
  (if (= (wm:cfg 'corner-auto) 1)
    (foreach found nodes
      (if (= (length (caddr found)) 3)
        (progn
          (setq p (cadr found) neighbors (caddr found))
          (foreach tip (mapcar '(lambda (v) (wm:add p v))
            (list (list sx sy) (list sx (- sy)) (list (- sx) sy) (list (- sx) (- sy))))
            (setq key (wm:key tip))
            (if (and (not (assoc key nodes)) (not (member key tips))
                (wm:inside tip poly) (setq normal (wm:tip-normal tip (wm:sub tip p)))
                (= (length (setq parts (wm:clip p tip poly))) 1)
                (equal (caar parts) p 1e-5) (equal (cadar parts) tip 1e-5))
              (progn
                (setq a p b tip)
                (if (> (car a) (car b)) (setq swap a a b b swap))
                (setq extra (cons (list (strcat (wm:key a) "/" (wm:key b)) a b) extra)
                  tips (cons key tips) wm:extensions (1+ wm:extensions)
                  wm:cuts (cons (list key key "EYE" tip normal) wm:cuts))))))))) extra)
;; Centre the largest lattice that fits an axis-aligned rectangular inset.
;; Fixed zero phase previously dropped an otherwise admissible cell column.
;; Keep the requested diagonals and minimum retreat; no stretching or clipping.
;; Non-rectangular polygons retain their exact whole-edge containment checks.
(defun wm:rect-layout (poly sx sy / xs ys xmin xmax ymin ymax cols rows)
  (setq xs (mapcar 'car poly) ys (mapcar 'cadr poly)
    xmin (apply 'min xs) xmax (apply 'max xs) ymin (apply 'min ys) ymax (apply 'max ys))
  (if (and (= (length poly) 4)
    (vl-every '(lambda (p) (and
      (or (equal (car p) xmin 1e-6) (equal (car p) xmax 1e-6))
      (or (equal (cadr p) ymin 1e-6) (equal (cadr p) ymax 1e-6)))) poly)
    (vl-every '(lambda (e) (or (equal (caar e) (caadr e) 1e-6)
      (equal (cadar e) (cadadr e) 1e-6))) (wm:edges poly)))
    (progn
      (setq cols (1+ (wm:floor (+ (/ (- xmax xmin (* 2.0 sx)) sx) 1e-8)))
        rows (1+ (wm:floor (+ (/ (- ymax ymin (* 2.0 sy)) sy) 1e-8))))
      (if (and (> cols 0) (> rows 0))
        (list cols rows
          (list (/ (- (+ xmin xmax) (* (1- cols) sx)) 2.0)
                (/ (- (+ ymin ymax) (* (1- rows) sy)) 2.0))
          ;; Even parity has the extra cell when both counts are odd.
          ;; Otherwise retain odd parity; the tied upper row ends at the right.
          (if (and (= (rem cols 2) 1) (= (rem rows 2) 1)) 0 1))))))
(defun wm:mesh (poly / xs ys xmin xmax ymin ymax sx sy nx ny row col row0 col0 centre verts ed a b key edges nodes found neighbors v p info kind half pair extra layout phase parity)
  (setq xs (mapcar 'car poly) ys (mapcar 'cadr poly) xmin (apply 'min xs) xmax (apply 'max xs) ymin (apply 'min ys) ymax (apply 'max ys)
    sx (/ (wm:cfg 'ml) 2.0) sy (/ (wm:cfg 'mw) 2.0)
    nx (+ 4 (fix (/ (- xmax xmin) sx))) ny (+ 4 (fix (/ (- ymax ymin) sy))) edges nil nodes nil wm:cells 0)
  (setq layout (wm:rect-layout poly sx sy) phase '(0.0 0.0) parity 1)
  (if layout
    (setq nx (car layout) ny (cadr layout) phase (caddr layout)
      parity (nth 3 layout) row0 0 col0 0)
    (setq row0 (1- (wm:floor (/ ymin sy))) col0 (1- (wm:floor (/ xmin sx)))))
  (if (> (* nx ny) (wm:cfg 'maxnodes)) (wm:fail "Surface trop grande : limite de securite 15000 noeuds. Diviser le panneau."))
  (setq row row0)
  (repeat ny
    (setq col col0)
    (repeat nx
      (if (= (abs (rem (+ row col) 2)) parity)
        (progn (setq centre (wm:add phase (list (* col sx) (* row sy)))
          verts (mapcar '(lambda (v) (wm:add centre v)) (list (list (- sx) 0.0) (list 0.0 sy) (list sx 0.0) (list 0.0 (- sy)))))
          ;; A cell is admitted only if all four vertices and all its edges fit.
          (if (and (vl-every '(lambda (v) (wm:inside v poly)) verts)
            (vl-every '(lambda (ed) (and (= (length (wm:clip (car ed) (cadr ed) poly)) 1)
              (equal (car (car (wm:clip (car ed) (cadr ed) poly))) (car ed) 1e-5)
              (equal (cadr (car (wm:clip (car ed) (cadr ed) poly))) (cadr ed) 1e-5))) (wm:edges verts)))
            (progn (setq wm:cells (1+ wm:cells)) (foreach ed (wm:edges verts)
              (setq a (car ed) b (cadr ed))
              (if (> (car a) (car b)) (setq v a a b b v))
              (setq key (strcat (wm:key a) "/" (wm:key b)))
              (if (not (assoc key edges))
                (progn (setq edges (cons (list key a b) edges))
                  (foreach pair (list (list a b) (list b a))
                    (setq p (car pair) key (wm:key p) found (assoc key nodes))
                    (if found (setq nodes (subst (list key p (cons (cadr pair) (caddr found))) found nodes))
                      (setq nodes (cons (list key p (list (cadr pair))) nodes)))))))))))
      (setq col (1+ col))) (setq row (1+ row)))
  (setq extra (wm:missing-edges nodes poly sx sy) edges (append extra edges)
    half (wm:half))
  (foreach ed edges
    (setq a (wm:add (cadr ed) (list half 0.0)) b (wm:sub (caddr ed) (list half 0.0)))
    (wm:draw (wm:bezier a
      (wm:add a (list (if (= (wm:cfg 'woven) 1) (min 8.0 (* 0.16 (wm:cfg 'ml))) 8.0) 0.0))
      (wm:sub b (list (if (= (wm:cfg 'woven) 1) (min 8.0 (* 0.16 (wm:cfg 'ml))) 8.0) 0.0)) b) (wm:cfg 'wire) nil))
  (foreach found nodes
    (setq p (cadr found) neighbors (caddr found) kind nil)
    (if (= (length neighbors) 2)
      (progn (setq info (wm:near p wm:inner) kind (if (> (abs (car (cadr info))) 0.7071) "LOOP" "EYE"))
        (setq wm:cuts (cons (list (car found) (car found) kind p) wm:cuts))))
    (if (/= kind "EYE")
      (progn
        (if (and (= (wm:cfg 'woven) 1) (= kind "LOOP"))
          (wm:draw (list (wm:sub p (list half 0.0)) (wm:add p (list half 0.0))) (wm:cfg 'wire) nil)
          (wm:insert wm:bead p 0.0))
        (setq wm:nodes (1+ wm:nodes)))))
  (princ))
(defun wm:back (pts / edges e ts s t0 mid run seg)
  (foreach e (mapcar 'list pts (cdr pts))
    (setq ts (wm:breaks (car e) (cadr e) (list wm:inner wm:outer)))
    (while (cdr ts)
      (setq s (car ts) t0 (cadr ts) mid (wm:lerp (car e) (cadr e) (/ (+ s t0) 2.0)))
      (if (or (wm:inside mid wm:inner) (not (wm:inside mid wm:outer)))
        (progn (setq seg (list (wm:lerp (car e) (cadr e) s) (wm:lerp (car e) (cadr e) t0)))
          (if (and run (< (distance (car run) (car seg)) 1e-5)) (setq run (cons (cadr seg) run))
            (progn (if run (wm:draw (reverse run) (wm:cfg 'lace) nil)) (setq run (list (cadr seg) (car seg))))))
        (progn (if run (wm:draw (reverse run) (wm:cfg 'lace) nil)) (setq run nil)))
      (setq ts (cdr ts))))
  (if run (wm:draw (reverse run) (wm:cfg 'lace) nil)))
(defun wm:at (chain poly / per e len a b out)
  (setq per 0.0) (foreach e (wm:edges poly) (setq per (+ per (distance (car e) (cadr e)))))
  (setq chain (rem (+ chain per) per))
  (foreach e (wm:edges poly)
    (if (not out) (progn (setq a (car e) b (cadr e) len (distance a b))
      (if (<= chain len) (setq out (list (wm:lerp a b (/ chain len)) (wm:unit (wm:sub b a))))
        (setq chain (- chain len)))))) out)
;; Find exactly one real convex corner between consecutive perimeter anchors.
;; Small turns from tessellated arcs, concave corners and like terminals retain
;; the classic lacing. Chain distances also handle the closing polygon edge.
(defun wm:corner (pair per / edges previous e chain delta hits t1 t2)
  (if (and (= (wm:cfg 'corner-auto) 1)
           (/= (caddar pair) (caddr (cadr pair))))
    (progn
      (setq edges (wm:edges wm:inner) previous (car (reverse edges)) chain 0.0 hits nil)
      (foreach e edges
        (setq delta (rem (+ (- chain (caar pair)) per) per)
          t1 (wm:unit (wm:sub (cadr previous) (car previous)))
          t2 (wm:unit (wm:sub (cadr e) (car e))))
        (if (and (> delta 1e-5) (< delta (- wm:pitch 1e-5))
                 (< (wm:dot t1 t2) 0.8660254))
          (setq hits (cons (list (car e) t1 t2 delta
            (> (wm:cross t1 t2) 1e-6)) hits)))
        (setq chain (+ chain (distance (car e) (cadr e))) previous e))
      (if (and (= (length hits) 1) (nth 4 (car hits))) (car hits)))))
;; Measure the frame locally, independent of tube width and polygon rotation.
(defun wm:frame-at (chain / info n ray ts e v outer)
  (setq info (wm:at chain wm:inner)
    n (list (cadr (cadr info)) (- (car (cadr info))))
    ray (wm:add (car info) (wm:mul n 10000.0)) ts nil)
  (foreach e (wm:edges wm:outer)
    (if (setq v (wm:hit (car info) ray (car e) (cadr e)))
      (if (> v 1e-7) (setq ts (cons v ts)))))
  (if ts
    (progn (setq outer (wm:lerp (car info) ray (apply 'min ts)))
      (list (wm:lerp (car info) outer 0.5) (cadr info)
        (distance (car info) outer) outer))))
;; Bridge the side / top (or bottom) behind the frame, without an extra turn
;; around its outside corner. Leg visibility agrees with adjacent windings.
;; Both visible fragments belong to one conceptual lacing path.
;; Perimeter winding invariant: one front leg and one rear leg per anchor.
;; Both LOOP and EYE have an incoming front leg and an outgoing rear leg.
(defun wm:leg-record (anchor visible / key found item)
  (setq key (wm:key anchor) found (assoc key wm:visibility)
    item (if found found (list key 0 0)))
  (setq item (list key (+ (cadr item) (if visible 1 0)) (+ (caddr item) (if visible 0 1))))
  (setq wm:visibility (if found (subst item found wm:visibility) (cons item wm:visibility))))
(defun wm:leg (pts anchor visible)
  (wm:leg-record anchor visible)
  (if visible (wm:draw pts (wm:cfg 'lace) nil) (wm:back pts)))
(defun wm:corner-legs (front rear pair / p np)
  (setq p (cadar pair) np (cadadr pair))
  (if (= (caddar pair) "EYE")
    (progn (wm:leg front p nil) (wm:leg rear np T))
    (progn (wm:leg front np T) (wm:leg rear p nil))))
;; Round a supplementary corner bridge on the actual outer tube face.
;; The rounding and all control handles follow its measured local width.
(defun wm:corner-return (pair bridge width / eye loop info t0 n dir radius rise ef er peak df db cf cb k h hp hn front rear cap eye-front)
  (setq eye (if (= (caddar pair) "EYE") (cadar pair) (cadadr pair))
    loop (if (= (caddar pair) "LOOP") (cadar pair) (cadadr pair))
    info (wm:near bridge wm:outer) t0 (cadr info)
    n (list (cadr t0) (- (car t0)))
    dir (if (> (wm:dot t0 (wm:sub loop eye)) 0.0) t0 (wm:mul t0 -1.0))
    radius (min (* width 0.16) (* (distance eye loop) 0.14)) rise (* radius 0.33)
    ef (wm:sub bridge (wm:mul dir radius)) er (wm:add bridge (wm:mul dir radius))
    peak (wm:add bridge (wm:mul n rise)) k 0.55228475
    df (wm:unit (wm:sub ef eye)) db (wm:unit (wm:sub loop er))
    cf (min (* k radius) (/ (* k rise) (max 0.25 (abs (wm:dot df n)))))
    cb (min (* k radius) (/ (* k rise) (max 0.25 (abs (wm:dot db n)))))
    h (min (* width 0.35) (* (distance eye loop) 0.22))
    hp (min (* width 0.16) (* (distance eye bridge) 0.12))
    hn (min (* width 0.35) (* (distance eye loop) 0.13) (* (distance loop bridge) 0.25))
    info (wm:near eye wm:inner) t0 (cadr info)
    front (wm:bezier eye (wm:add eye (wm:mul (list (cadr t0) (- (car t0))) hp))
      (wm:sub ef (wm:mul df h)) ef)
    rear (wm:bezier er (wm:add er (wm:mul db h)) (wm:sub loop (wm:mul dir hn)) loop)
    cap (append (wm:bezier ef (wm:add ef (wm:mul df cf)) (wm:sub peak (wm:mul dir (* k radius))) peak)
      (cdr (wm:bezier peak (wm:add peak (wm:mul dir (* k radius))) (wm:sub er (wm:mul db cb)) er)))
    eye-front (= (caddar pair) "LOOP"))
  (wm:leg-record eye eye-front) (wm:leg-record loop (not eye-front))
  (if eye-front
    (progn (wm:draw (append front (cdr cap)) (wm:cfg 'lace) nil) (wm:back rear))
    (progn (wm:back front) (wm:draw (append cap (cdr rear)) (wm:cfg 'lace) nil))))
(defun wm:corner-lace (pair corner / start delta f1 f2 q s t1 t2 det v r rail front rear p np rad a b qo so bridge)
  (setq start (caar pair) delta (cadddr corner)
    f1 (wm:frame-at (+ start (* delta 0.5)))
    f2 (wm:frame-at (+ start delta (* (- wm:pitch delta) 0.5))))
  (if (and f1 f2)
    (progn
      (setq q (car f1) s (car f2) t1 (cadr f1) t2 (cadr f2)
        det (wm:cross t1 t2))
      (if (> (abs det) 1e-8)
        (progn
          (setq v (/ (wm:cross (wm:sub s q) t2) det)
            r (wm:add q (wm:mul t1 v))
            rad (min (* 0.15 (min (caddr f1) (caddr f2)))
              (* 0.3 (distance q r)) (* 0.3 (distance r s)))
            a (wm:sub r (wm:mul t1 rad)) b (wm:add r (wm:mul t2 rad))
            rail (append (list q) (wm:bezier a
              (wm:add a (wm:mul t1 (* rad 0.55)))
              (wm:sub b (wm:mul t2 (* rad 0.55))) b) (list s)))
          ;; A narrow or irregular outer contour can invalidate this bridge.
          ;; In that case use the original return; never draw through the net.
          (if (vl-every '(lambda (a) (and (wm:inside a wm:outer)
                                         (not (wm:inside a wm:inner)))) rail)
            (progn
              (setq p (cadar pair) np (cadadr pair)
                qo (cadddr f1) so (cadddr f2))
              (if (or (and (= (caddar pair) "EYE") (nth 3 (car pair)))
                      (and (= (caddr (cadr pair)) "EYE") (nth 3 (cadr pair))))
                (progn
                  ;; The new eye already receives the lateral lacing from the
                  ;; preceding interval. This interval MUST go to the top/bottom
                  ;; face, not return a second time to the same lateral face.
                  (setq bridge (wm:frame-at (caddr (wm:near (wm:lerp p np 0.5) wm:inner))))
                  (if (and bridge (> (abs (car (cadr bridge))) 0.7071))
                    (setq bridge (cadddr bridge))
                    (setq bridge (if (= (caddar pair) "EYE") so qo)))
                  (wm:corner-return pair bridge (min (caddr f1) (caddr f2))))
                (progn
              (if (= (caddar pair) "EYE")
                (setq front (wm:bezier p (wm:lerp p qo 0.3) (wm:lerp p qo 0.7) qo)
                  rear (wm:bezier so
                    (wm:add so (wm:add (wm:mul t2 (* 0.6 (caddr f2)))
                      (wm:mul (list (cadr t2) (- (car t2))) (* -0.08 (caddr f2)))))
                    (wm:lerp so np 0.7) np))
                (setq front (wm:bezier so (wm:lerp so np 0.3) (wm:lerp so np 0.7) np)
                  rear (wm:bezier qo
                    (wm:add qo (wm:add (wm:mul t1 (* -0.6 (caddr f1)))
                      (wm:mul (list (cadr t1) (- (car t1))) (* -0.08 (caddr f1)))))
                    (wm:lerp qo p 0.7) p)))
              ;; Match the adjacent straight windings at BOTH anchors.
              ;; Match incoming-front / outgoing-rear at the two anchors.
              (wm:corner-legs front rear pair)
              (wm:back (append (list qo) rail (list so)))
                ))
              (setq wm:corners (1+ wm:corners)) T)))))))
(defun wm:lace (poly / anchors pair p nextp info normal tangent outerp ray ts v sign index pitch per phase edge1 edge2 radius rise arc peak side width turn-info normal-p normal-next h hp hn front-path back-path k e corner soft hug frontdir backdir cf cb)
  (setq anchors (vl-sort wm:anchors '(lambda (a b) (< (car a) (car b))))
    index 0 wm:corners 0 wm:visibility nil wm:boundary (length anchors) sign (if (> (wm:area wm:inner) 0) 1.0 -1.0) per 0.0 k 0.55228475)
  (foreach e (wm:edges wm:inner) (setq per (+ per (distance (car e) (cadr e)))))
  (foreach pair (mapcar 'list anchors (append (cdr anchors) (list (car anchors))))
    (setq p (cadar pair) nextp (cadadr pair) pitch (- (caadr pair) (caar pair)))
    (if (<= pitch 0) (setq pitch (+ pitch per)))
    (setq wm:pitch pitch corner (wm:corner pair per))
    (if (not (and corner (wm:corner-lace pair corner)))
      (progn
    (setq phase (+ (caar pair) (* 0.46 pitch)) info (wm:at phase wm:inner) tangent (cadr info)
      normal (wm:mul (list (cadr tangent) (- (car tangent))) sign)
      ray (wm:add (car info) (wm:mul normal 10000.0)) ts nil)
    (foreach e (wm:edges wm:outer) (if (setq v (wm:hit (car info) ray (car e) (cadr e))) (if (> v 1e-7) (setq ts (cons v ts)))))
    (if (not ts) (wm:fail "Le contour exterieur ne permet pas de retrouver le cadre a cette rive."))
    (setq outerp (wm:lerp (car info) ray (apply 'min ts)) width (distance (car info) outerp)
      turn-info (wm:near outerp wm:outer) tangent (cadr turn-info)
      normal (wm:mul (list (cadr tangent) (- (car tangent))) sign)
      side (> (abs (car normal)) (abs (cadr normal)))
      soft (and (not side) (= (caddar pair) "LOOP") (= (caddr (cadr pair)) "LOOP"))
      hug (and side (= (caddar pair) "EYE") (= (caddr (cadr pair)) "EYE")))
    ;; Actual local frame width drives both the return and the rounding.
    ;; The spacing between successive mesh vertices also limits the loop size.
    (setq radius (min (* width (cond (hug 0.10) (side 0.14) (soft 0.16) (T 0.28)))
        (* pitch (cond (hug 0.16) (soft 0.14) (T 0.18))))
      ;; At the side turn the INNER edge of the cable touches the profile.
      ;; Diameter supplies the centreline offset; frame width supplies the span.
      rise (if hug (/ (wm:cfg 'lace) 2.0) (* radius (cond (side 0.85) (soft 0.33) (T 0.50))))
      edge1 (wm:sub outerp (wm:mul tangent radius)) edge2 (wm:add outerp (wm:mul tangent radius))
      peak (wm:add outerp (wm:mul normal rise))
      info (wm:near p wm:inner) normal-p (if (nth 3 (car pair)) (nth 3 (car pair)) (wm:mul (list (cadr (cadr info)) (- (car (cadr info)))) sign))
      info (wm:near nextp wm:inner) normal-next (if (nth 3 (cadr pair)) (nth 3 (cadr pair)) (wm:mul (list (cadr (cadr info)) (- (car (cadr info)))) sign))
      h (min (* width 0.35) (* pitch 0.22))
      hp (min (* width 0.16) (* (distance p outerp) 0.12))
      hn (min (* width 0.16) (* (distance nextp outerp) 0.12)))
    ;; Two joined quarter-ellipses; tangents agree with both cable legs.
    ;; Free top/bottom lacing: a shallow return aligned with the oblique legs.
    ;; Local measured frame width and attachment pitch limit every handle.
    ;; Horizontal tangents at the mesh loops remove the pointed V-shaped cusp.
    (if (or soft hug)
      (progn
        (setq frontdir (wm:unit (wm:sub (if hug nextp p) (if hug edge2 edge1)))
          backdir (wm:unit (wm:sub (if hug p nextp) (if hug edge1 edge2)))
          cf (min (* k radius) (/ (* k rise) (max 0.25 (abs (wm:dot frontdir normal)))))
          cb (min (* k radius) (/ (* k rise) (max 0.25 (abs (wm:dot backdir normal)))))
          hp (min (* width 0.35) (* pitch 0.13) (* (distance p outerp) 0.25))
          hn (min (* width 0.35) (* pitch 0.13) (* (distance nextp outerp) 0.25)))
        (setq arc (wm:bezier edge1 (wm:sub edge1 (wm:mul (if hug backdir frontdir) (if hug cb cf)))
          (wm:sub peak (wm:mul tangent (* k radius))) peak))
        (setq arc (append arc (cdr (wm:bezier peak (wm:add peak (wm:mul tangent (* k radius)))
          (wm:sub edge2 (wm:mul (if hug frontdir backdir) (if hug cf cb))) edge2)))))
      (progn
        (setq arc (wm:bezier edge1 (wm:add edge1 (wm:mul normal (* k rise)))
          (wm:sub peak (wm:mul tangent (* k radius))) peak))
        (setq arc (append arc (cdr (wm:bezier peak (wm:add peak (wm:mul tangent (* k radius)))
          (wm:add edge2 (wm:mul normal (* k rise))) edge2))))))
    (if side
      (if hug
        (setq back-path (wm:bezier p (wm:add p (wm:mul normal-p hp))
            (wm:add edge1 (wm:mul backdir h)) edge1)
          front-path (wm:bezier edge2 (wm:add edge2 (wm:mul frontdir h))
            (wm:add nextp (wm:mul normal-next hn)) nextp))
        (setq back-path (wm:bezier p (wm:add p (wm:mul normal-p hp)) (wm:sub edge1 (wm:mul normal h)) edge1)
          front-path (wm:bezier edge2 (wm:sub edge2 (wm:mul normal h)) (wm:add nextp (wm:mul normal-next hn)) nextp)))
      (if soft
        (setq back-path (wm:bezier nextp (wm:sub nextp (wm:mul tangent hn))
            (wm:add edge2 (wm:mul backdir h)) edge2)
          front-path (wm:bezier edge1 (wm:add edge1 (wm:mul frontdir h))
            (wm:add p (wm:mul tangent hp)) p))
        (setq back-path (wm:bezier nextp (wm:add nextp (wm:mul normal-next hn)) (wm:sub edge2 (wm:mul normal h)) edge2)
          front-path (wm:bezier edge1 (wm:sub edge1 (wm:mul normal h)) (wm:add p (wm:mul normal-p hp)) p))))
    ;; Visibility comes from the anchor type, also on mixed fallback intervals.
    (wm:leg back-path (if side p nextp)
      (if side nil T))
    (wm:leg-record (if side nextp p)
      (if side T nil))
    (if (if side T nil)
      ;; Keep a single continuous polyline for the visible turn and leg.
      (wm:draw (append (if side arc (reverse arc)) (cdr front-path)) (wm:cfg 'lace) nil)
      (progn (wm:draw (if side arc (reverse arc)) (wm:cfg 'lace) nil) (wm:back front-path)))
    (if (and (= (caddar pair) "EYE") (= (rem index (wm:cfg 'stops)) 0))
      (wm:insert "JHR_WEBNET_BUTEE_4x4_V1" (wm:lerp p edge1 0.16) (angle p edge1)))
    ))
    (setq index (1+ index)))
  (if (or (/= (length wm:visibility) (length anchors))
    (not (vl-every '(lambda (rec) (and (= (cadr rec) 1) (= (caddr rec) 1))) wm:visibility)))
    (wm:fail "Alternance de lacage incoherente : chaque attache doit avoir un brin avant et un brin arriere.")))
(defun wm:block (name shapes / data)
  (if (tblsearch "BLOCK" name) (wm:fail "Nom de bloc deja utilise."))
  (setq wm:changed T)
  (entmake (list '(0 . "BLOCK") '(8 . "0") (cons 2 name) '(70 . 0) '(10 0.0 0.0 0.0)))
  (foreach data shapes (if (not (entmake data)) (wm:fail "Creation d un composant impossible.")))
  (entmake '((0 . "ENDBLK") (8 . "0"))))
(defun wm:bead-block (name w h / shapes x y r verts)
  (if (not (tblsearch "BLOCK" name))
    (progn (setq x (/ w 2.0) y (/ h 2.0) r 0.45
      verts (list (list (- x) (- r y)) (list (- r x) (- y)) (list (- x r) (- y)) (list x (- r y))
        (list x (- y r)) (list (- x r) y) (list (- r x) y) (list (- x) (- y r))))
      (setq shapes (list (wm:pline-data verts 0.12 T)
        (wm:pline-data (list (list (+ (- x) 0.7) (+ (- y) 0.5)) (list (+ (- x) 0.7) (- y 0.5))) 0.10 nil)
        (wm:pline-data (list (list (- x 0.7) (+ (- y) 0.5)) (list (- x 0.7) (- y 0.5))) 0.10 nil)))
      (wm:block name shapes))))
(defun wm:weave-block (name / half width shapes strand j u p run previous sign)
 (if (not (tblsearch "BLOCK" name))
  (progn
   (setq half (wm:half) width (wm:cfg 'wire) shapes nil)
   (foreach strand '(1.0 -1.0)
    (setq j 0 run nil)
    (repeat 65
     (setq u (/ j 64.0) p (list (+ (- half) (* 2 half u)) (* strand width 0.35 (sin (* 4 pi u)))))
     ;; Small breaks alternate at crossings to show which rope passes underneath.
     (if (and (> j 1) (< j 63) (< (abs (sin (* 4 pi u))) 0.28)
          (< (* strand (cos (* 4 pi u))) 0.0))
      (progn (if (> (length run) 1) (setq shapes (cons (wm:pline-data (reverse run) width nil) shapes))) (setq run nil))
      (setq run (cons p run)))
     (setq j (1+ j)))
    (if (> (length run) 1) (setq shapes (cons (wm:pline-data (reverse run) width nil) shapes))))
   (wm:block name (reverse shapes)))))
(defun wm:eye-block (/ name outline holes pts j ang)
  (setq name "JHR_WEBNET_OEIL_0150_B16_H8_3_V1")
  (if (not (tblsearch "BLOCK" name))
    (progn (setq pts '((0.0 -2.0) (8.0 -4.15)) j 0)
      (repeat 17 (setq ang (+ (- (/ pi 2.0)) (* pi (/ j 16.0)))
        pts (append pts (list (list (+ 11.85 (* 4.15 (cos ang))) (* 4.15 (sin ang))))) j (1+ j)))
      (setq pts (append pts '((8.0 4.15) (0.0 2.0))))
      (wm:block name (list (wm:pline-data pts 0.15 T) (wm:pline-data (wm:circle-points '(12.0 0.0) 1.5) 0.12 T)
        (wm:pline-data '((1.5 -1.6) (1.5 1.6)) 0.10 nil) (wm:pline-data '((3.0 -1.6) (3.0 1.6)) 0.10 nil))))))
(defun wm:offset (en gap / obj results valid sign raw o p candidates)
  (setq obj (vlax-ename->vla-object en) valid nil)
  (foreach sign '(-1 1)
    (if (not valid)
      (progn (setq raw (vl-catch-all-apply 'vlax-invoke (list obj 'Offset (* sign gap))))
        (if (not (vl-catch-all-error-p raw))
          (progn (if raw (setq wm:changed T)) (setq candidates nil) (foreach o raw
            (setq wm:temps (cons o wm:temps) p (wm:poly (vlax-vla-object->ename o)))
            (if (and (> (abs (wm:area p)) 1.0) (< (abs (wm:area p)) (abs (wm:area wm:inner)))
                 (vl-every '(lambda (q) (wm:inside q wm:inner)) p)) (setq candidates (cons p candidates))))
          (if (> (length candidates) 1) (wm:fail "Le retrait divise le filet en plusieurs panneaux. Traiter chaque panneau separement."))
          (if candidates (setq valid (car candidates))))))))
  (if (not valid) (wm:fail "Retrait du filet impossible. Reduire le retrait ou verifier la polyligne interieure.")) valid)
(defun wm:validate (en / data)
  (setq data (entget en))
  (if (or (/= (cdr (assoc 0 data)) "LWPOLYLINE") (= (logand 1 (cdr (assoc 70 data))) 0))
    (wm:fail "Selectionner une polyligne 2D fermee."))
  (if (and (assoc 210 data) (not (equal (cdr (assoc 210 data)) '(0.0 0.0 1.0) 1e-8)))
    (wm:fail "Les contours doivent etre dessines dans le plan XY (normale Z).")) en)
(defun wm:selfcross (p / ed i j bad a b)
  (setq ed (wm:edges p) i 0 bad nil)
  (foreach a ed (setq j 0)
    (foreach b ed
      (if (and (> j (+ i 1)) (not (and (= i 0) (= j (1- (length ed))))) (wm:hit (car a) (cadr a) (car b) (cadr b))) (setq bad T))
      (setq j (1+ j))) (setq i (1+ i))) bad)
(defun wm:generate (inside outside / obj lo hi poly name index data ins first last shapes result)
  (setq wm:reason nil)
  (wm:settings-valid) (wm:validate inside) (wm:validate outside)
  (if (equal inside outside) (wm:fail "Les deux contours doivent etre differents."))
  (if (> (abs (- (cond ((cdr (assoc 38 (entget inside)))) (T 0.0)) (cond ((cdr (assoc 38 (entget outside)))) (T 0.0)))) 0.01)
    (wm:fail "Les deux contours doivent etre coplanaires."))
  (setq obj (vlax-ename->vla-object inside)) (vla-GetBoundingBox obj 'lo 'hi)
  (setq lo (vlax-safearray->list lo) hi (vlax-safearray->list hi)
    wm:origin (mapcar '(lambda (a b) (/ (+ a b) 2.0)) (list (car lo) (cadr lo)) (list (car hi) (cadr hi)))
    wm:angle (wm:cfg 'angle) wm:inner (wm:poly inside) wm:outer (wm:poly outside))
  (if (< (wm:area wm:inner) 0) (setq wm:inner (reverse wm:inner)))
  (if (< (wm:area wm:outer) 0) (setq wm:outer (reverse wm:outer)))
  (if (or (wm:selfcross wm:inner) (wm:selfcross wm:outer)) (wm:fail "Contour croise ou auto-intersectant."))
  (if (or (not (vl-every '(lambda (p) (wm:inside p wm:outer)) wm:inner))
          (vl-some '(lambda (a) (vl-some '(lambda (b) (wm:hit (car a) (cadr a) (car b) (cadr b))) (wm:edges wm:outer))) (wm:edges wm:inner)))
    (wm:fail "Le contour exterieur doit entourer strictement le contour interieur sans le couper."))
  (setq poly (wm:offset inside (wm:cfg 'gap)) wm:netpoly poly wm:anchors nil wm:cuts nil wm:shapes nil wm:nodes 0 wm:boundary 0
    wm:bead (if (= (wm:cfg 'woven) 1)
      (strcat "JHR_MAILLE_TRESSE_D" (vl-string-translate "." "_" (rtos (wm:cfg 'wire) 2 3)) "_V1")
      (strcat "JHR_WEBNET_DOUILLE_" (vl-string-translate "." "_" (rtos (wm:cfg 'sleeve-l) 2 2)) "x"
        (vl-string-translate "." "_" (rtos (wm:cfg 'sleeve-h) 2 2)) "_V1")))
  (princ (if (= (wm:cfg 'woven) 1) "\nCreation de la maille tressee sans bagues..." "\nCreation de la maille et des douilles...")) (wm:mesh poly)
  (wm:terminals)
  (if (< (length wm:anchors) 4) (wm:fail "Cadre trop petit pour ces dimensions de maille."))
  (wm:lace poly)
  (wm:eye-block)
  (if (= (wm:cfg 'woven) 1) (wm:weave-block wm:bead) (wm:bead-block wm:bead (wm:cfg 'sleeve-l) (wm:cfg 'sleeve-h)))
  (wm:bead-block "JHR_WEBNET_BUTEE_4x4_V1" 4.0 4.0)
  (setq name (rf:panel-name "PANNEAU_FILET_INOX_" outside)) (wm:block name (reverse wm:shapes))
  (setq data (wm:insert-data name wm:origin wm:angle))
  (setq data (subst (cons 8 (getvar "CLAYER")) (assoc 8 data) data)
    data (subst (cons 10 (list (car wm:origin) (cadr wm:origin) (caddr lo))) (assoc 10 data) data))
  (entmake data) (setq ins (entlast))
  (regapp "JHR_WEBNET")
  (entmod (append (entget ins) (list (list -3 (list "JHR_WEBNET" (cons 1000 (strcat "representation2D;maille_centre_centre;accessoires_schematiques;mode=" (if (= (wm:cfg 'woven) 1) "tresse" "bagues")))
    (cons 1040 (wm:cfg 'wire)) (cons 1040 (wm:cfg 'lace)) (cons 1040 (wm:cfg 'mw)) (cons 1040 (wm:cfg 'ml))
    (cons 1005 (cdr (assoc 5 (entget inside)))) (cons 1005 (cdr (assoc 5 (entget outside)))))))))
  (if (wm:product-xdata)
   (entmod (subst (list -3 (append (cadr (assoc -3 (entget ins '("JHR_WEBNET")))) (wm:product-xdata)))
    (assoc -3 (entget ins '("JHR_WEBNET"))) (entget ins '("JHR_WEBNET")))))
  (setq *wm:last* ins)
  (princ (strcat "\n" name " : " (itoa wm:cells) " losanges complets, " (itoa wm:nodes) (if (= (wm:cfg 'woven) 1) " jonctions de maille sans bagues, " " douilles de maille, ") (itoa wm:boundary) " raccords de rive, " (itoa wm:corners) " transitions d angle, " (itoa wm:extensions) " brins avec oeillet ajoutes. Tout le contenu est sur le calque 0.")) ins)
(defun wm:cleanup () (foreach o wm:temps (vl-catch-all-apply 'vla-Delete (list o))) (setq wm:temps nil))
(defun c:JHRMAILLECLI (/ *error* doc inside outside result single wm:temps wm:origin wm:angle wm:inner wm:outer wm:netpoly wm:shapes wm:anchors wm:nodes wm:boundary wm:bead wm:cuts wm:eyes wm:loops wm:corners wm:extensions wm:pitch wm:visibility begun wm:reason wm:changed)
 (defun *error* (msg)
  (wm:cleanup) (if begun (vla-EndUndoMark doc))
  (if wm:reason (princ (strcat "\nPanneau non cree : " wm:reason)))
  (if (and (not wm:reason) msg (not (wcmatch (strcase msg) "*CANCEL*,*QUIT*,*BREAK*,*ANNUL*"))) (princ (strcat "\nPanneau non cree : " msg))) (princ))
 (if (not (member (getvar "INSUNITS") '(0 4))) (wm:fail "Dessiner en millimetres avant de lancer JHRMAILLE."))
 (if (not (= (getvar "TILEMODE") 1)) (wm:fail "Lancer la commande dans l espace objet."))
 (setq single (and (= *wm:tool* 1) (= (fix (nth 7 (rf:opts))) 0)))
 (setq inside (car (entsel (if single "\nContour FERME de la taille totale du panneau : " "\n1 - Contour FERME interieur du cadre : "))))
 (if inside (progn (wm:validate inside)
  (setq outside (if single inside (car (entsel "\n2 - Contour FERME exterieur : limite totale du panneau : "))))
  (if outside (progn
   (setq doc (vla-get-ActiveDocument (vlax-get-acad-object))) (vla-StartUndoMark doc) (setq begun T)
   (setq result (vl-catch-all-apply 'rf:dispatch (list inside outside))) (wm:cleanup)
   (vla-EndUndoMark doc) (setq begun nil)
   (if (vl-catch-all-error-p result)
    (progn (if wm:changed (command-s "_.UNDO" "1")) (princ (strcat "\nPanneau non cree : " (if wm:reason wm:reason (vl-catch-all-error-message result)))))
    (progn (vla-Regen doc 1) (princ "\nUn panneau ajoute ; contours sources conserves. ANNULER revient en une etape."))))))) (princ))
(defun wm:ask (k label / val)
  (initget 6) (setq val (getreal (strcat "\n" label " <" (rtos (wm:cfg k) 2 2) "> : ")))
  (if val (wm:set k val)))
(defun c:JHRFILETPARAMCLI (/ a n mode)
  (foreach item '((mw "Petite diagonale centre / centre (mm)") (ml "Grande diagonale centre / centre (mm)")
      (wire "Diametre cable de maille (mm)") (lace "Diametre cable de lacage (mm)") (gap "Retrait filet / face interieure du cadre (mm)")
      (sleeve-l "Longueur dessinee de la douille (mm)") (sleeve-h "Largeur dessinee de la douille (mm)"))
    (wm:ask (car item) (cadr item)))
  (setq a (getangle (strcat "\nDirection de la grande diagonale <" (rtos (* 180.0 (/ (wm:cfg 'angle) pi)) 2 1) " deg> : ")))
  (if a (wm:set 'angle (+ a (angle '(0 0 0) (trans '(1 0 0) 1 0 T)))))
  (initget 6) (setq n (getint (strcat "\nPas des petites butees de rive <" (itoa (wm:cfg 'stops)) "> : ")))
  (if n (wm:set 'stops n))
  (initget "Auto Classique")
  (setq mode (getkword (strcat "\nRaccords d angle [Auto/Classique] <"
    (if (= (wm:cfg 'corner-auto) 1) "Auto" "Classique") "> : ")))
  (if mode (wm:set 'corner-auto (if (= mode "Auto") 1 0)))
  (princ "\nParametres memorises pour cette session. Lancer JHRMAILLE.") (princ))
(if (not (boundp '*rf:mask*)) (setq *rf:mask* 0))
(defun wm:ui (/ dll result keys vals product)
 (if (not (member "JHR:MAILLE-DIALOG-V133R1" (atoms-family 1)))
  (progn
   (setq dll (if *wm:ui-root* (strcat *wm:ui-root* "/JhrMailleUi_v1_3_3r1.dll") (findfile "JhrMailleUi_v1_3_3r1.dll")))
   (if (or (not dll) (not (findfile dll)))
    (wm:fail "Interface absente. NETLOAD JhrMailleUi_v1_3_3r1.dll du dossier complet, ou utiliser JHRMAILLECLI."))
   (command-s "_.NETLOAD" dll)))
 (if (not (member "JHR:MAILLE-DIALOG-V133R1" (atoms-family 1)))
  (wm:fail "Interface non chargee. Verifier le chargement .NET, ou utiliser JHRMAILLECLI."))
 (setq product (wm:product-current))
 (setq result (apply 'jhr:maille-dialog-v133r1
  (append (list (wm:cfg 'ml) (wm:cfg 'mw) (wm:cfg 'wire) (wm:cfg 'lace) (wm:cfg 'gap)
   (* 180.0 (/ (wm:cfg 'angle) pi)) (wm:cfg 'woven) (wm:cfg 'corner-auto)
   (wm:cfg 'sleeve-l) (wm:cfg 'sleeve-h) (wm:cfg 'stops) (if product (car product) ""))
   (list *wm:tool*) *wm:patterns* (list *rf:mask*))))
 ;; The managed ResultBuffer wraps a Nil value as (nil), not nil.
 (if (equal result '(nil)) (setq result nil))
 (if result
  (progn
   (if (or (/= (length result) 40)
       (not (vl-every 'numberp (rf:take 11 result)))
       (not (vl-every '(lambda (x) (= (type x) 'STR)) (rf:take 3 (wm:tail 11 result))))
       (not (vl-every 'numberp (wm:tail 14 result))))
    (wm:fail "Reponse invalide de l interface. Aucun parametre modifie."))
   (setq keys '(ml mw wire lace gap angle woven corner-auto sleeve-l sleeve-h stops) vals result)
   (while keys
    (wm:set (car keys) (cond ((= (car keys) 'angle) (* pi (/ (car vals) 180.0)))
      ((member (car keys) '(woven corner-auto stops)) (fix (car vals))) (T (car vals))))
    (setq keys (cdr keys) vals (cdr vals)))
   (setq *wm:product* (if (/= (nth 11 result) "") (rf:take 3 (wm:tail 11 result)) nil)
     *wm:product-stamp* (if *wm:product* (wm:product-stamp) nil)
     *wm:tool* (fix (nth 14 result)) *wm:patterns* (rf:take 24 (wm:tail 15 result)) *rf:mask* (fix (nth 39 result))) T)))
(defun c:JHRMAILLE (/ *error* wm:reason)
 (defun *error* (msg) (if wm:reason (princ (strcat "\n" wm:reason))) (princ))
 (if (not (member (getvar "INSUNITS") '(0 4))) (wm:fail "Dessiner en millimetres avant de lancer JHRMAILLE."))
 (if (/= (getvar "TILEMODE") 1) (wm:fail "Lancer la commande dans l espace objet."))
 (if (wm:ui) (c:JHRMAILLECLI) (princ "\nAnnule. Aucun objet ni parametre modifie.")) (princ))
(defun c:JHRMAILLEPARAM (/ *error* wm:reason)
 (defun *error* (msg) (if wm:reason (princ (strcat "\n" wm:reason))) (princ))
 (if (wm:ui) (princ "\nParametres memorises pour cette session. Lancer JHRMAILLE.")
   (princ "\nAnnule. Parametres conserves.")) (princ))
(defun rf:prepare (inside outside ang / obj lo hi)
  (setq wm:reason nil)
  (wm:validate inside) (wm:validate outside)
  (if (and (equal inside outside) (not (and (= *wm:tool* 1) (= (fix (nth 7 (rf:opts))) 0)))) (wm:fail "Les deux contours doivent etre differents."))
  (if (> (abs (- (cond ((cdr (assoc 38 (entget inside)))) (T 0.0)) (cond ((cdr (assoc 38 (entget outside)))) (T 0.0)))) 0.01)
    (wm:fail "Les deux contours doivent etre coplanaires."))
  (setq obj (vlax-ename->vla-object inside)) (vla-GetBoundingBox obj 'lo 'hi)
  (setq lo (vlax-safearray->list lo) hi (vlax-safearray->list hi)
    wm:origin (mapcar '(lambda (a b) (/ (+ a b) 2.0)) (list (car lo) (cadr lo)) (list (car hi) (cadr hi)))
    wm:angle ang wm:inner (wm:poly inside) wm:outer (wm:poly outside))
  (if (< (wm:area wm:inner) 0) (setq wm:inner (reverse wm:inner)))
  (if (< (wm:area wm:outer) 0) (setq wm:outer (reverse wm:outer)))
  (if (or (wm:selfcross wm:inner) (wm:selfcross wm:outer)) (wm:fail "Contour croise ou auto-intersectant."))
  (if (and (not (equal inside outside)) (or (not (vl-every '(lambda (p) (wm:inside p wm:outer)) wm:inner))
          (vl-some '(lambda (a) (vl-some '(lambda (b) (wm:hit (car a) (cadr a) (car b) (cadr b))) (wm:edges wm:outer))) (wm:edges wm:inner))))
    (wm:fail "Le contour exterieur doit entourer strictement le contour interieur sans le couper."))
  lo)

;; Other filling tools. Cable geometry is preserved; new panels use descriptive names.
(defun rf:take (n items / out) (repeat n (setq out (cons (car items) out) items (cdr items))) (reverse out))
(defun rf:opts () (rf:take 8 (wm:tail (* 8 (1- *wm:tool*)) *wm:patterns*)))
(defun rf:setopts (values / head tail)
 (setq head (rf:take (* 8 (1- *wm:tool*)) *wm:patterns*) tail (wm:tail (* 8 *wm:tool*) *wm:patterns*))
 (setq *wm:patterns* (append head values tail)))
(defun rf:validate (v / a b wire thick gap ang margin mode)
 (setq a (nth 0 v) b (nth 1 v) wire (nth 2 v) thick (nth 3 v) gap (nth 4 v) ang (nth 5 v) margin (nth 6 v) mode (fix (nth 7 v)))
 (if (or (<= a 0) (<= b 0) (<= wire 0) (<= thick 0) (< gap 0) (< margin 0) (> (abs ang) 360) (/= (nth 7 v) mode))
  (wm:fail "Parametres du remplissage invalides."))
 (cond
  ((= *wm:tool* 1) (if (or (>= wire a) (< mode 0) (> mode 2)) (wm:fail "Le fil doit etre plus petit que l ouverture libre ; mode 0=un contour, 1=deux visibles, 2=deux caches.")))
  ((= *wm:tool* 2) (if (or (< a b) (>= wire (/ (min a b) 3.0)) (< mode 0) (> mode 1) (>= margin (/ a 2.0))) (wm:fail "Verifier les diagonales et la largeur de laniere du deploye.")))
  ((= *wm:tool* 3) (if (or (>= a b) (< mode 0) (> mode 2)) (wm:fail "Le trou doit etre plus petit que l entraxe.")))
  (T (wm:fail "Outil de remplissage inconnu."))) v)
(defun rf:offset (en gap / wm:inner) (setq wm:inner (wm:poly en)) (wm:offset en gap))
(defun rf:bounds (poly) (list (apply 'min (mapcar 'car poly)) (apply 'min (mapcar 'cadr poly))
 (apply 'max (mapcar 'car poly)) (apply 'max (mapcar 'cadr poly))))
(defun rf:limit (nx ny) (if (> (* nx ny) 15000) (wm:fail "Motif trop dense : limite de 15000 positions. Diviser le panneau ou augmenter le pas.")))
(defun rf:stroke (a b poly width / parts part)
 (setq parts (wm:clip a b poly))
 (foreach part parts (if (> (distance (car part) (cadr part)) 1e-7) (progn (wm:draw part width nil) (setq rf:count (1+ rf:count))))))

(defun rf:panel-name (stem en / obj lo hi dim index)
 (setq obj (vlax-ename->vla-object en)) (vla-GetBoundingBox obj 'lo 'hi)
 (setq lo (vlax-safearray->list lo) hi (vlax-safearray->list hi)
  dim (strcat (rtos (- (car hi) (car lo)) 2 2) "x" (rtos (- (cadr hi) (cadr lo)) 2 2)) index 1)
 (while (tblsearch "BLOCK" (strcat stem dim "_" (itoa index))) (setq index (1+ index)))
 (strcat stem dim "_" (itoa index)))
(defun rf:panel-name-poly (stem poly / box dim index)
 (setq box (rf:bounds (mapcar '(lambda (q) (wm:add wm:origin (wm:rot q wm:angle))) poly))
  dim (strcat (rtos (- (nth 2 box) (nth 0 box)) 2 2) "x" (rtos (- (nth 3 box) (nth 1 box)) 2 2)) index 1)
 (while (tblsearch "BLOCK" (strcat stem dim "_" (itoa index))) (setq index (1+ index)))
 (strcat stem dim "_" (itoa index)))
(defun rf:hidden-type ()
 (if (not (tblsearch "LTYPE" "JHR_CACHE"))
  (progn (setq wm:changed T)
   (entmake '((0 . "LTYPE") (100 . "AcDbSymbolTableRecord") (100 . "AcDbLinetypeTableRecord")
    (2 . "JHR_CACHE") (70 . 0) (3 . "JHR - fils derriere le cadre, 4 / 2 mm") (72 . 65) (73 . 2) (40 . 6.0)
    (49 . 4.0) (74 . 0) (49 . -2.0) (74 . 0))))))
(defun rf:edge-draw (a b hidden / data)
 (if (> (distance a b) 1e-7)
  (progn (setq data (wm:pline-data (list a b) 0.0 nil))
   (if hidden (setq data (subst '(6 . "JHR_CACHE") (assoc 6 data) data)))
   (setq wm:shapes (cons data wm:shapes) rf:count (1+ rf:count)))))
(defun rf:wire-edge (a b opts / parts part v vv ts lo hi mid t0 t1)
 (if (/= (fix (nth 7 opts)) 2) (rf:edge-draw a b nil)
  (progn (setq v (wm:sub b a) vv (wm:dot v v) ts '(0.0 1.0) parts (wm:clip a b wm:inner))
   (foreach part parts (foreach q part (setq ts (cons (max 0.0 (min 1.0 (/ (wm:dot (wm:sub q a) v) vv))) ts))))
   (setq ts (vl-sort ts '<))
   (while (cdr ts) (setq t0 (car ts) t1 (cadr ts) mid (wm:lerp a b (/ (+ t0 t1) 2.0)))
    (rf:edge-draw (wm:lerp a b t0) (wm:lerp a b t1) (not (wm:inside mid wm:inner))) (setq ts (cdr ts))))))
(defun rf:grid-axis (lo hi step / count first)
 ;; Keep the specified pitch, centre the full wires and finish within an opening.
 ;; For a rectangle, each edge has at least half an opening beyond the last wire.
 (setq count (max 1 (wm:floor (/ (- hi lo) step)))
  first (/ (- (+ lo hi) (* (1- count) step)) 2.0))
 (list first count))
(defun rf:back-edge (a b first count step radius opts / v dy ts k y edge t0 t1 mid index)
 ;; Remove the back family's silhouette wherever a front horizontal wire covers it.
 ;; This also works on oblique end cuts and on separate concave contour segments.
 (setq v (wm:sub b a) dy (cadr v) ts '(0.0 1.0) k 0)
 (if (> (abs dy) 1e-10)
  (repeat count (setq y (+ first (* k step)))
   (foreach edge (list (- y radius) (+ y radius))
    (setq t0 (/ (- edge (cadr a)) dy))
    (if (and (> t0 0.0) (< t0 1.0)) (setq ts (cons t0 ts))))
   (setq k (1+ k))))
 (setq ts (vl-sort ts '<))
 (while (cdr ts)
  (setq t0 (car ts) t1 (cadr ts) mid (wm:lerp a b (/ (+ t0 t1) 2.0))
   index (wm:floor (+ 0.5 (/ (- (cadr mid) first) step))))
  (if (not (and (>= index 0) (< index count)
           (<= (abs (- (cadr mid) (+ first (* index step)))) (+ radius 1e-8))))
   (rf:wire-edge (wm:lerp a b t0) (wm:lerp a b t1) opts))
  (setq ts (cdr ts))))
(defun rf:strip-caps (poly pos radius vertical first count step opts / e a b av bv dv lo hi t0 t1 p0 p1)
 ;; The boundary of panel intersect wire-strip closes each cut at its real angle.
 (foreach e (wm:edges poly)
  (setq a (car e) b (cadr e) av (if vertical (car a) (cadr a))
   bv (if vertical (car b) (cadr b)) dv (- bv av) lo 0.0 hi 1.0)
  (if (< (abs dv) 1e-10)
   (if (or (< av (- pos radius)) (> av (+ pos radius))) (setq hi -1.0))
   (progn (setq t0 (/ (- (- pos radius) av) dv) t1 (/ (- (+ pos radius) av) dv)
    lo (max 0.0 (min t0 t1)) hi (min 1.0 (max t0 t1)))))
  (if (> hi (+ lo 1e-9))
   (progn (setq p0 (wm:lerp a b lo) p1 (wm:lerp a b hi))
    (if vertical (rf:back-edge p0 p1 first count step radius opts)
     (rf:wire-edge p0 p1 opts))))))
(defun rf:wipeout-data (poly / box size base pts)
 (setq box (rf:bounds poly) size (max (- (nth 2 box) (nth 0 box)) (- (nth 3 box) (nth 1 box)))
  base (list (nth 0 box) (nth 1 box) 0.0)
  pts (mapcar '(lambda (p) (list (- (/ (- (car p) (car base)) size) 0.5)
    (- 0.5 (/ (- (cadr p) (cadr base)) size)) 0.0)) poly))
 (append (list '(0 . "WIPEOUT") '(100 . "AcDbEntity") '(8 . "0") '(62 . 256) '(370 . -1)
  '(100 . "AcDbWipeout") '(90 . 0) (cons 10 base) (cons 11 (list size 0.0 0.0))
  (cons 12 (list 0.0 size 0.0)) '(13 1.0 1.0 0.0) '(70 . 7) '(280 . 1) '(281 . 50) '(282 . 50)
  '(283 . 0) '(290 . 0) '(71 . 2) (cons 91 (1+ (length pts))))
  (mapcar '(lambda(p) (cons 14 p)) (append pts (list (car pts))))))
(defun rf:triangles (poly / pts out found i prev cur next triangle other)
 ;; Ear clipping yields convex pieces for masks even on concave panel contours.
 (setq pts poly)
 (if (< (wm:area pts) 0) (setq pts (reverse pts)))
 (while (> (length pts) 3)
  (setq found nil i 0)
  (while (and (not found) (< i (length pts)))
   (setq prev (nth (rem (+ i (1- (length pts))) (length pts)) pts) cur (nth i pts)
    next (nth (rem (1+ i) (length pts)) pts) triangle (list prev cur next))
   (cond
    ((< (abs (wm:cross (wm:sub cur prev) (wm:sub next cur))) 1e-9)
     (setq pts (vl-remove cur pts) found T))
    ((and (> (wm:cross (wm:sub cur prev) (wm:sub next cur)) 0.0)
      (not (vl-some '(lambda(p) (and (not (member p triangle)) (wm:inside p triangle))) pts)))
     (setq out (cons triangle out) pts (vl-remove cur pts) found T)))
   (setq i (1+ i)))
  (if (not found) (wm:fail "Contour du masquage impossible a decouper.")))
 (if (= (length pts) 3) (setq out (cons pts out))) out)
(defun rf:plane-clip (poly axis limit greater / prev cur a b ia ib t0 out)
 (setq prev (last poly))
 (foreach cur poly
  (setq a (nth axis prev) b (nth axis cur) ia (if greater (>= a limit) (<= a limit))
   ib (if greater (>= b limit) (<= b limit)))
  (if (not (equal ia ib))
   (setq t0 (/ (- limit a) (- b a)) out (cons (wm:lerp prev cur t0) out)))
  (if ib (setq out (cons cur out))) (setq prev cur))
 (reverse out))
(defun rf:mask-strip (triangles axis pos radius / tri cut)
 (foreach tri triangles
  (setq cut (rf:plane-clip tri axis (- pos radius) T))
  (if cut (setq cut (rf:plane-clip cut axis (+ pos radius) nil)))
  (if (and (> (length cut) 2) (> (abs (wm:area cut)) 1e-8))
   (progn (setq rf:masks (cons (rf:wipeout-data cut) rf:masks))
    (if (> (length rf:masks) 3000) (wm:fail "Masquage trop dense : diviser le panneau ou augmenter le pas."))))))
(defun rf:square (poly opts / box step d radius gx gy x0 y0 nx ny k x y side part maskpoly triangles)
 (setq box (rf:bounds poly) step (+ (nth 0 opts) (nth 2 opts)) d (nth 2 opts) radius (/ d 2.0)
  gx (rf:grid-axis (nth 0 box) (nth 2 box) step) gy (rf:grid-axis (nth 1 box) (nth 3 box) step)
  x0 (car gx) nx (cadr gx) y0 (car gy) ny (cadr gy))
 (rf:limit (+ 3 nx) (+ 3 ny))
 (if (or (<= (- (nth 2 box) (nth 0 box)) d) (<= (- (nth 3 box) (nth 1 box)) d))
  (wm:fail "Le panneau est trop petit pour le diametre du fil."))
 (if (= (fix (nth 7 opts)) 2) (rf:hidden-type))
 (setq maskpoly (if (= (fix (nth 7 opts)) 0) poly wm:inner))
 (if (= *rf:mask* 1) (setq triangles (rf:triangles maskpoly)))
 (if (= *rf:mask* 2) (setq rf:masks (list (rf:wipeout-data maskpoly))))
 ;; Horizontal wires are the front family. Diameter is shown by two thin edges.
 (setq k 0)
 (repeat nx (setq x (+ x0 (* k step)))
  (if triangles (rf:mask-strip triangles 0 x radius))
  (foreach side '(-1.0 1.0)
   (foreach part (wm:clip (list (+ x (* side radius)) (nth 1 box)) (list (+ x (* side radius)) (nth 3 box)) poly)
    (rf:back-edge (car part) (cadr part) y0 ny step radius opts)))
  (rf:strip-caps poly x radius T y0 ny step opts)
  (setq k (1+ k)))
 (setq k 0)
 (repeat ny (setq y (+ y0 (* k step)))
  (if triangles (rf:mask-strip triangles 1 y radius))
  (foreach side '(-1.0 1.0)
   (foreach part (wm:clip (list (nth 0 box) (+ y (* side radius))) (list (nth 2 box) (+ y (* side radius))) poly)
    (rf:wire-edge (car part) (cadr part) opts)))
  (rf:strip-caps poly y radius nil y0 ny step opts)
  (setq k (1+ k))))

(defun rf:bond (opts)
 (if (> (nth 6 opts) 0.0) (nth 6 opts)
  (min (* 0.35 (nth 0 opts)) (max (* 2.0 (nth 2 opts)) (min (* 0.12 (nth 0 opts)) (* 0.25 (nth 1 opts)))))))
(defun rf:convex-inset (pts gap / lines e dir normal shifted prev current det t0 out)
 (if (< (wm:area pts) 0) (setq pts (reverse pts)))
 (foreach e (wm:edges pts)
  (setq dir (wm:sub (cadr e) (car e)) normal (wm:mul (list (- (cadr dir)) (car dir)) (/ gap (wm:len dir)))
   lines (cons (list (wm:add (car e) normal) dir) lines)))
 (setq lines (reverse lines) prev (last lines))
 (foreach current lines
  (setq det (wm:cross (cadr prev) (cadr current)))
  (if (< (abs det) 1e-8) (wm:fail "Laniere ou plat de jonction incompatible avec ces diagonales."))
  (setq t0 (/ (wm:cross (wm:sub (car current) (car prev)) (cadr current)) det)
   out (cons (wm:add (car prev) (wm:mul (cadr prev) t0)) out) prev current))
 (reverse out))
(defun rf:round-hole (pts radius / prev cur next incoming outgoing len offset a b q j out)
 (setq prev (last pts))
 (foreach pair (mapcar 'list pts (append (cdr pts) (list (car pts))))
  (setq cur (car pair) next (cadr pair) incoming (wm:unit (wm:sub prev cur)) outgoing (wm:unit (wm:sub next cur))
   offset (min radius (* 0.20 (distance cur prev)) (* 0.20 (distance cur next)))
   a (wm:add cur (wm:mul incoming offset)) b (wm:add cur (wm:mul outgoing offset)) j 0)
  ;; Quadratic corner rounding, five vertices; all long edges and node flats remain straight.
  (repeat 5 (setq q (/ (float j) 4.0))
   (setq out (cons (wm:add (wm:add (wm:mul a (* (- 1.0 q) (- 1.0 q))) (wm:mul cur (* 2.0 q (- 1.0 q)))) (wm:mul b (* q q))) out) j (1+ j)))
  (setq prev cur)) (reverse out))
(defun rf:expanded-hole (opts / sx sy half pts inset)
 (setq sx (/ (nth 0 opts) 2.0) sy (/ (nth 1 opts) 2.0) half (/ (rf:bond opts) 2.0)
  pts (list (list (- (- sx half)) 0.0) (list (- half) sy) (list half sy)
   (list (- sx half) 0.0) (list half (- sy)) (list (- half) (- sy))))
 (setq inset (rf:convex-inset pts (/ (nth 2 opts) 2.0)))
 (if (or (<= (abs (wm:area inset)) 1e-5) (not (vl-every '(lambda(q) (wm:inside q pts)) inset)))
  (wm:fail "La laniere ferme la maille. Reduire sa largeur ou le plat de jonction."))
 (rf:round-hole inset (* 0.65 (nth 2 opts))))
(defun rf:box-overlap (a b) (and (<= (nth 0 a) (nth 2 b)) (<= (nth 0 b) (nth 2 a)) (<= (nth 1 a) (nth 3 b)) (<= (nth 1 b) (nth 3 a))))
(defun rf:hole-outline (hole plate / e part)
 (if (rf:fits hole plate)
  (progn (wm:draw hole 0.0 T) (setq rf:count (1+ rf:count)))
  (foreach e (wm:edges hole) (foreach part (wm:clip (car e) (cadr e) plate) (rf:edge-draw (car part) (cadr part) nil)))))
(defun rf:material-edge (a b holes / cuts hole parts part dir size intervals lo hi cursor)
 (setq dir (wm:sub b a) size (wm:dot dir dir))
 (foreach hole holes
  (if (rf:box-overlap (rf:bounds (list a b)) (car hole))
   (foreach part (wm:clip a b (cadr hole))
    (setq lo (/ (wm:dot (wm:sub (car part) a) dir) size) hi (/ (wm:dot (wm:sub (cadr part) a) dir) size))
    (if (> (- hi lo) 1e-8) (setq intervals (cons (list (max 0.0 lo) (min 1.0 hi)) intervals))))))
 (setq intervals (vl-sort intervals '(lambda(x y) (< (car x) (car y)))) cursor 0.0)
 (foreach part intervals
  (if (> (car part) cursor) (rf:edge-draw (wm:lerp a b cursor) (wm:lerp a b (car part)) nil))
  (setq cursor (max cursor (cadr part))))
 (if (< cursor 1.0) (rf:edge-draw (wm:lerp a b cursor) b nil)))
(defun rf:expanded (poly opts / box sx sy col row col0 col1 row0 row1 base p hole holes hb e)
 (setq box (rf:bounds poly) sx (/ (nth 0 opts) 2.0) sy (/ (nth 1 opts) 2.0)
  col0 (1- (wm:floor (/ (nth 0 box) sx))) col1 (+ 2 (fix (/ (nth 2 box) sx)))
  row0 (1- (wm:floor (/ (nth 1 box) sy))) row1 (+ 2 (fix (/ (nth 3 box) sy))))
 (rf:limit (1+ (- col1 col0)) (1+ (- row1 row0)))
 (setq base (rf:expanded-hole opts) row row0)
 (while (<= row row1) (setq col col0)
  (while (<= col col1)
   (if (/= (rem (+ row col) 2) 0)
    (progn (setq p (list (* col sx) (* row sy)) hole (mapcar '(lambda(q) (wm:add p q)) base) hb (rf:bounds hole))
     (if (rf:box-overlap hb box) (progn (setq holes (cons (list hb hole) holes)) (rf:hole-outline hole poly)))))
   (setq col (1+ col))) (setq row (1+ row)))
 ;; Draw only material at the cut; openings remain open where they meet the frame.
 (foreach e (wm:edges poly) (rf:material-edge (car e) (cadr e) holes)))
(defun rf:fits (pts poly / e seg segments total ok)
 (setq ok (vl-every '(lambda (p) (wm:inside p poly)) pts))
 (if ok (foreach e (wm:edges pts)
  (setq segments (wm:clip (car e) (cadr e) poly) total 0.0)
  (foreach seg segments (setq total (+ total (distance (car seg) (cadr seg)))))
  (if (> (- (distance (car e) (cadr e)) total) 1e-7) (setq ok nil)))) ok)
(defun rf:hole-name (a mode) (strcat "JHR_PERFORATION_" (if (= mode 2) "C" "R") (vl-string-translate "." "_" (rtos a 2 6))))
(defun rf:hole-block (a mode / radius shape)
 (setq radius (/ a 2.0))
 (setq shape (if (= mode 2)
  (wm:pline-data (list (list (- radius) (- radius)) (list radius (- radius)) (list radius radius) (list (- radius) radius)) 0.0 T)
  (list '(0 . "CIRCLE") '(100 . "AcDbEntity") '(8 . "0") '(62 . 256) '(6 . "Continuous") '(370 . -1)
   '(100 . "AcDbCircle") '(10 0.0 0.0 0.0) (cons 40 radius))))
 (if (not (tblsearch "BLOCK" (rf:hole-name a mode))) (wm:block (rf:hole-name a mode) (list shape))))
(defun rf:perforated (plate poly opts / box a pitch dy mode radius row col row0 row1 col0 col1 p pts halfshift fits)
 (setq box (rf:bounds poly) a (nth 0 opts) pitch (nth 1 opts) mode (fix (nth 7 opts)) radius (/ a 2.0)
  dy (* pitch (if (= mode 1) (/ (sqrt 3.0) 2.0) 1.0))
  col0 (1- (wm:floor (/ (nth 0 box) pitch))) col1 (1+ (fix (/ (nth 2 box) pitch)))
  row0 (1- (wm:floor (/ (nth 1 box) dy))) row1 (1+ (fix (/ (nth 3 box) dy))))
 (rf:limit (1+ (- col1 col0)) (1+ (- row1 row0)))
 (setq row row0) (while (<= row row1) (setq col col0 halfshift (if (and (= mode 1) (/= (rem row 2) 0)) (/ pitch 2.0) 0.0))
  (while (<= col col1)
   (setq p (list (+ (* col pitch) halfshift) (* row dy)))
   (setq fits (if (= mode 2)
    (rf:fits (mapcar '(lambda(q) (wm:add p q)) (list (list (- radius) (- radius)) (list radius (- radius)) (list radius radius) (list (- radius) radius))) poly)
    (and (wm:inside p poly) (>= (distance p (car (wm:near p poly))) (- radius 1e-7)))))
   (if fits (progn (wm:insert (rf:hole-name a mode) p 0.0) (setq rf:count (1+ rf:count))))
   (setq col (1+ col))) (setq row (1+ row)))
 (if (= rf:count 0) (wm:fail "Aucune perforation complete ne tient avec cette bordure."))
 (wm:draw plate 0.0 T) (rf:hole-block a mode))
(defun rf:designation (v / a b w th mode)
 (setq a (rtos (nth 0 v) 2 3) b (rtos (nth 1 v) 2 3) w (rtos (nth 2 v) 2 3) th (rtos (nth 3 v) 2 3) mode (fix (nth 7 v)))
 (cond ((= *wm:tool* 1) (strcat "Grillage soude carre;ouverture=" a ";fil=" w ";pas=" (rtos (+ (nth 0 v) (nth 2 v)) 2 3) ";mm"))
  ((= *wm:tool* 2) (strcat "Metal deploye;ML=" a ";MW=" b ";laniere_projection=" w ";plat_jonction=" (rtos (rf:bond v) 2 3) ";epaisseur=" th ";aspect=" (if (= mode 0) "aplati" "relief") ";mm"))
  (T (strcat "Tole perforee;" (cond ((= mode 2) "C/U") ((= mode 1) "R/T60") (T "R/U")) ";trou=" a ";entraxe=" b ";epaisseur=" th ";mm"))))
(defun rf:generate (inside outside / opts lo plate poly inset name stem index data ins rf:count rf:masks)
 (setq wm:reason nil opts (rf:validate (rf:opts)))
 (if (and (= *wm:tool* 1) (= (fix (nth 7 opts)) 0)) (setq outside inside))
 (setq lo (rf:prepare inside outside (* pi (/ (nth 5 opts) 180.0))))
 (setq wm:shapes nil rf:count 0)
 (setq plate (if (> (nth 4 opts) 1e-8) (rf:offset (if (= *wm:tool* 1) outside inside) (nth 4 opts)) (if (= *wm:tool* 1) wm:outer wm:inner)))
 ;; Buffer half the projected strand width to keep all thick strokes inside the panel.
 (setq inset (+ (nth 4 opts) (cond ((= *wm:tool* 3) (nth 6 opts)) (T 0.0))))
 (setq poly (if (> inset 1e-8) (rf:offset (if (= *wm:tool* 1) outside inside) inset) (if (= *wm:tool* 1) wm:outer wm:inner)))
 (cond ((= *wm:tool* 1) (rf:square poly opts)) ((= *wm:tool* 2) (rf:expanded poly opts)) ((= *wm:tool* 3) (rf:perforated plate poly opts)))
 (if (= rf:count 0) (wm:fail "Aucun motif ne tient dans ce panneau."))
 (setq stem (cond ((= *wm:tool* 1) "PANNEAU_GRILLAGE_CARRE_") ((= *wm:tool* 2) "PANNEAU_METAL_DEPLOYE_") (T "PANNEAU_TOLE_PERFOREE_")))
 (setq name (rf:panel-name-poly stem plate)) (wm:block name (append (reverse rf:masks) (reverse wm:shapes)))
 (setq data (wm:insert-data name wm:origin wm:angle)
  data (subst (cons 8 (getvar "CLAYER")) (assoc 8 data) data)
  data (subst (cons 10 (list (car wm:origin) (cadr wm:origin) (caddr lo))) (assoc 10 data) data))
 (entmake data) (setq ins (entlast)) (regapp "JHR_REMPLISSAGE")
 (entmod (append (entget ins) (list (list -3 (append (list "JHR_REMPLISSAGE" (cons 1000 "representation2D;parametres_mm;pas_de_fixations_ajoutees") (cons 1070 *wm:tool*) (cons 1000 (rf:designation opts)))
  (mapcar '(lambda(v) (cons 1040 v)) opts) (list (cons 1005 (cdr (assoc 5 (entget inside)))) (cons 1005 (cdr (assoc 5 (entget outside))))))))))
 (setq *wm:last* ins *rf:last-count* rf:count)
 (princ (strcat "\n" name " : " (itoa rf:count) (if (= *wm:tool* 3) " perforations completes." " segments de remplissage.") " Bloc sur calque courant ; contenu calque 0 / DuCalque.")) ins)
(defun rf:dispatch (inside outside) (if (= *wm:tool* 0) (wm:generate inside outside) (rf:generate inside outside)))
(defun c:JHRMAILLEPARAMCLI (/ choice opts labels out i val mask)
 (initget "Filet Carre Deploye Perfore")
 (setq choice (getkword "\nOutil [Filet/Carre/Deploye/Perfore] <dernier outil> : "))
 (if choice (setq *wm:tool* (cond ((= choice "Filet") 0) ((= choice "Carre") 1) ((= choice "Deploye") 2) (T 3))))
 (if (= *wm:tool* 0) (c:JHRFILETPARAMCLI)
  (progn (setq opts (rf:opts) i 0 out nil
   labels (cond ((= *wm:tool* 1) '("Ouverture libre carree" nil "Diametre fil" nil "Retrait cadre" "Orientation degres" nil "Selection : 0=un contour, 1=deux visibles, 2=deux caches"))
    ((= *wm:tool* 2) '("Grande diagonale ML" "Petite diagonale MW" "Largeur laniere en projection" "Epaisseur" "Retrait cadre" "Orientation degres" "Plat de jonction (0=auto)" "Aspect : 0=aplati, 1=relief"))
    (T '("Diametre ou cote du trou" "Entraxe" nil "Epaisseur" "Retrait cadre" "Orientation degres" "Bordure pleine" "Type : 0=R/U, 1=R/T, 2=C/U"))))
   (foreach label labels (setq val (if label (getreal (strcat "\n" label " <" (rtos (nth i opts) 2 2) "> : "))) out (cons (if val val (nth i opts)) out) i (1+ i)))
   (setq out (reverse out)) (if (= *wm:tool* 1) (setq out (cons (car out) (cons (car out) (cddr out))))) (rf:validate out) (rf:setopts out)
   (if (= *wm:tool* 1)
    (progn (initget "Aucun Fils Surface")
     (setq mask (getkword (strcat "\nMasquage [Aucun/Fils/Surface] <" (nth *rf:mask* '("Aucun" "Fils" "Surface")) "> : ")))
     (if mask (setq *rf:mask* (cond ((= mask "Fils") 1) ((= mask "Surface") 2) (T 0))))))
   (princ "\nParametres memorises. Lancer JHRMAILLECLI."))) (princ))

(princ "\nJHRMAILLE : choisir l outil et le mode de contours, puis creer un panneau. JHRMAILLEPARAM : interface seule. JHRMAILLECLI : sans interface.")
(princ)

; JHR .NET 1.4 : bridge, old CLI remains available when the plugin is absent.
(defun c:JHRMAILLE (/ result)
 (setq result (vl-catch-all-apply 'jhr:maille-net-create-v140 nil))
 (if (vl-catch-all-error-p result) (c:JHRMAILLECLI))
 (princ))

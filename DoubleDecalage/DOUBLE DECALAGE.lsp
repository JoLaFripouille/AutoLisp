(vl-load-com)
(defun c:DDC ( / val_offset del_ent js ent vla_obj)
 (initget 6)
(setq val_offset (getdist (strcat "\nLargeur totale du décalage [b]<[/b]" (rtos (getvar "USERR1")) "[b]>[/b]:")))
(if (not val_offset) (setq val_offset (getvar "USERR1")) (setvar "USERR1" val_offset))
(initget "Oui Non _Yes No")
(setq del_ent (if (eq (getkword "\nSupprimer l'entité sélectionnée [Oui/Non] [b]<[/b]Non[b]>[/b]: ") "Yes") T nil))
(while (/= ent "Exit")
   (setq js (ssadd))
	(initget "Sortir _Exit")
	(while (or (null (setq ent (entsel "\nChoix de l'objet à décaler de part et d'autre/[sortir]: "))) (/= ent "Exit"))
		(cond
			((not (null ent))
				(setq ent (car ent))
				(setq vla_obj (vlax-ename->vla-object ent))
				(vla-Offset vla_obj (/ val_offset 2.0))
         (setq js (ssadd (entlast) js))
				(vla-Offset vla_obj (- (/ val_offset 2.0)))
				(setq js (ssadd (entlast) js))
				(if del_ent (entdel ent))
			)
		)
		(initget "Sortir _Exit")
	)
	(if js (sssetfirst nil js))
)
(princ)
)
